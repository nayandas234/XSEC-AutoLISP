;=========================================================
; XSEC PROJECT
; FILE : 02_UTILS.LSP
; PART : A
;=========================================================

(vl-load-com)

;----------------------------------------------------------
; PI
;----------------------------------------------------------

(setq *XSEC_PI* pi)

;----------------------------------------------------------
; Degree → Radian
;----------------------------------------------------------

(defun XSEC:Deg2Rad (a)

  (* pi (/ a 180.0))

)

;----------------------------------------------------------
; Radian → Degree
;----------------------------------------------------------

(defun XSEC:Rad2Deg (a)

  (/ (* a 180.0) pi)

)

;----------------------------------------------------------
; Point
;----------------------------------------------------------

(defun XSEC:Point
(
x
y
)

(list x y 0.0)

)

;----------------------------------------------------------
; X
;----------------------------------------------------------

(defun XSEC:X (p)

(car p)

)

;----------------------------------------------------------
; Y
;----------------------------------------------------------

(defun XSEC:Y (p)

(cadr p)

)

;----------------------------------------------------------
; Distance
;----------------------------------------------------------

(defun XSEC:Distance
(
p1
p2
)

(distance p1 p2)

)

;----------------------------------------------------------
; Mid Point
;----------------------------------------------------------

(defun XSEC:Mid
(
p1
p2
)

(list

(/ (+ (car p1)(car p2)) 2.0)

(/ (+ (cadr p1)(cadr p2)) 2.0)

0.0

)

)

;----------------------------------------------------------
; Polar
;----------------------------------------------------------

(defun XSEC:Polar
(
pt
ang
dis
)

(polar pt ang dis)

)

;----------------------------------------------------------
; Copy Point
;----------------------------------------------------------

(defun XSEC:CopyPoint
(
pt
)

(list

(car pt)

(cadr pt)

0.0

)

)

;----------------------------------------------------------
; Move Point
;----------------------------------------------------------

(defun XSEC:MovePoint
(
pt
dx
dy
)

(list

(+ (car pt) dx)

(+ (cadr pt) dy)

0.0

)

)

;----------------------------------------------------------
; Add X
;----------------------------------------------------------

(defun XSEC:AddX
(
pt
d
)

(list

(+ (car pt) d)

(cadr pt)

0.0

)

)

;----------------------------------------------------------
; Add Y
;----------------------------------------------------------

(defun XSEC:AddY
(
pt
d
)

(list

(car pt)

(+ (cadr pt) d)

0.0

)

)

;----------------------------------------------------------
; Round
;----------------------------------------------------------

(defun XSEC:Round (v p / m)

  (setq m (expt 10.0 p))

  (/ (float (fix (+ (* v m) 0.5))) m)

)

;----------------------------------------------------------
; Minimum X
;----------------------------------------------------------

(defun XSEC:MinX (pts)

  (apply 'min

    (mapcar

      '(lambda (p) (car p))

      pts

    )

  )

)

;----------------------------------------------------------
; Maximum X
;----------------------------------------------------------

(defun XSEC:MaxX (pts)

  (apply 'max

    (mapcar

      '(lambda (p) (car p))

      pts

    )

  )

)

;----------------------------------------------------------
; Minimum Y
;----------------------------------------------------------

(defun XSEC:MinY (pts)

  (apply 'min

    (mapcar

      '(lambda (p) (cadr p))

      pts

    )

  )

)

;----------------------------------------------------------
; Maximum Y
;----------------------------------------------------------

(defun XSEC:MaxY (pts)

  (apply 'max

    (mapcar

      '(lambda (p) (cadr p))

      pts

    )

  )

)

;----------------------------------------------------------
; Width
;----------------------------------------------------------

(defun XSEC:Width (pts)

  (- (XSEC:MaxX pts)

     (XSEC:MinX pts))

)

;----------------------------------------------------------
; Height
;----------------------------------------------------------

(defun XSEC:Height (pts)

  (- (XSEC:MaxY pts)

     (XSEC:MinY pts))

)

;----------------------------------------------------------
; Sort By Offset
;----------------------------------------------------------

(defun XSEC:SortOffset (pts)

  (vl-sort

    pts

    '(lambda (a b)

       (< (car a)

          (car b))

     )

  )

)

;----------------------------------------------------------
; Find Offset = 0
;----------------------------------------------------------

(defun XSEC:FindZeroPoint (pts / p)

  (setq p nil)

  (foreach x pts

    (if

      (equal

        (car x)

        0.0

        1e-8

      )

      (setq p x)

    )

  )

  p

)

;----------------------------------------------------------
; Left Most
;----------------------------------------------------------

(defun XSEC:LeftPoint (pts)

  (car

    (XSEC:SortOffset pts)

  )

)

;----------------------------------------------------------
; Right Most
;----------------------------------------------------------

(defun XSEC:RightPoint (pts)

  (car

    (last

      (XSEC:SortOffset pts)

    )

  )

)

;----------------------------------------------------------
; Copy List
;----------------------------------------------------------

(defun XSEC:CopyList (lst)

  (mapcar

    '(lambda (x) x)

    lst

  )

)

;----------------------------------------------------------
; Bounding Box
;----------------------------------------------------------

(defun XSEC:BoundingBox (pts /)

  (list
    (XSEC:MinX pts)
    (XSEC:MinY pts)
    (XSEC:MaxX pts)
    (XSEC:MaxY pts)
  )

)

;----------------------------------------------------------
; Shift Point List
;----------------------------------------------------------

(defun XSEC:ShiftPoints (pts dx dy / out)

  (setq out '())

  (foreach p pts

    (setq out

      (append out

        (list

          (list

            (+ (car p) dx)

            (+ (cadr p) dy)

            0.0

          )

        )

      )

    )

  )

  out

)

;----------------------------------------------------------
; Scale Point List
;----------------------------------------------------------

(defun XSEC:ScalePoints (pts sx sy / out)

  (setq out '())

  (foreach p pts

    (setq out

      (append out

        (list

          (list

            (* (car p) sx)

            (* (cadr p) sy)

            0.0

          )

        )

      )

    )

  )

  out

)

;----------------------------------------------------------
; Lowest RL
;----------------------------------------------------------

(defun XSEC:BottomRL (pts)

  (XSEC:MinY pts)

)

;----------------------------------------------------------
; Highest RL
;----------------------------------------------------------

(defun XSEC:TopRL (pts)

  (XSEC:MaxY pts)

)

;----------------------------------------------------------
; Find Crown Point
;----------------------------------------------------------

(defun XSEC:CrownPoint (pts / p y)

  (setq y (XSEC:MaxY pts))

  (setq p nil)

  (foreach x pts

    (if

      (equal

        (cadr x)

        y

        1e-8

      )

      (setq p x)

    )

  )

  p

)

;----------------------------------------------------------
; Find Bottom Point
;----------------------------------------------------------

(defun XSEC:BottomPoint (pts / p y)

  (setq y (XSEC:MinY pts))

  (setq p nil)

  (foreach x pts

    (if

      (equal

        (cadr x)

        y

        1e-8

      )

      (setq p x)

    )

  )

  p

)

;----------------------------------------------------------
; Find Nearest Point
;----------------------------------------------------------

(defun XSEC:NearestPoint (pt pts / d best dist)

  (setq d 1e99)
  (setq best nil)

  (foreach p pts

    (setq dist (distance pt p))

    (if (< dist d)

      (progn
        (setq d dist)
        (setq best p)
      )

    )

  )

  best

)

;----------------------------------------------------------
; Linear Interpolation
;----------------------------------------------------------

(defun XSEC:Interpolate

(

x

x1

y1

x2

y2

)

(+ y1

(*

(/ (- x x1)

(- x2 x1))

(- y2 y1)

)

)

)

(princ)
